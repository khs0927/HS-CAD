; Generated XiCAD loader. Do not edit XiCAD vendor files.
(command "_.OPTIONS" "_FILES" "_SUPPORT" "_ADD" "C:/cad/vendor/xicad/Lib" "")
(command "_.OPTIONS" "_FILES" "_SUPPORT" "_ADD" "C:/cad/vendor/xicad/DialogBox" "")
(command "_.OPTIONS" "_FILES" "_SUPPORT" "_ADD" "C:/cad/vendor/xicad/_ZWCad" "")

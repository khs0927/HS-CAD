(defun c:DrawMyLeaders ( / oldlayer)
  (setq oldlayer (getvar "CLAYER"))
  (command "-layer" "m" "치수" "")
  (command "_.QLEADER" (list 453000.0 210400.0) (list 454000.0 211200.0) (list 456000.0 211200.0) "" "T180 그라스울 판넬(지붕)" "")
  (command "_.QLEADER" (list 449650.0 205000.0) (list 448500.0 205500.0) (list 446000.0 205500.0) "" "T100 그라스울 벽판넬" "")
  (command "_.QLEADER" (list 450000.0 207000.0) (list 451500.0 207500.0) (list 453500.0 207500.0) "" "H-400x200x8x13" "")
  (setvar "CLAYER" oldlayer)
  (princ)
)

(defun c:ScanOrientalMaterials ( / ss i ent dxf txt file out-path )
  (setq out-path "C:/cad/zwcad-ai-modifier/oriental_materials.txt")
  (setq file (open out-path "w"))
  (if file
    (progn
      (write-line "=== NATIVE LISP MATERIAL AUDIT ===" file)
      (setq ss (ssget "X" '((0 . "TEXT,MTEXT"))))
      (if ss
        (progn
          (setq i 0)
          (while (< i (sslength ss))
            (setq ent (ssname ss i))
            (setq dxf (entget ent))
            (setq txt (cdr (assoc 1 dxf)))
            (if txt
              (progn
                (if (or (wcmatch (strcase txt) "*EPS*")
                        (wcmatch (strcase txt) "*THK*")
                        (wcmatch txt "*판넬*")
                        (wcmatch txt "*패널*")
                        (wcmatch txt "*지붕*")
                        (wcmatch txt "*벽*")
                        (wcmatch txt "*샌드위치*")
                        (wcmatch txt "*그라스울*")
                        (wcmatch txt "*우레탄*")
                        (wcmatch txt "*난연*")
                        (wcmatch txt "*철골*")
                        (wcmatch (strcase txt) "*H-*"))
                  (progn
                    (write-line (strcat "Layer: " (cdr (assoc 8 dxf)) " | Text: " txt) file)
                  )
                )
              )
            )
            (setq i (1+ i))
          )
        )
      )
      (close file)
      (princ "\n[SUCCESS] LISP Material Scan Complete!")
    )
    (princ "\n[ERROR] Failed to open output file.")
  )
  (princ)
)

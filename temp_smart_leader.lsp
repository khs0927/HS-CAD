(defun c:DrawSmartLeaders ( / oldlayer)
  (setq oldlayer (getvar "CLAYER"))
  (command "-layer" "m" "치수" "")
  (setvar "DIMTAD" 1)
  (command "_.LEADER" (list 218977.2 260400.0) (list 219977.2 261500.0) (list 222977.2 261500.0) "" "T180 그라스울 판넬(지붕)" "")
  (command "_.LEADER" (list 215627.2 255000.0) (list 214477.2 256000.0) (list 211477.2 256000.0) "" "T100 그라스울 벽판넬" "")
  (command "_.LEADER" (list 215977.2 257000.0) (list 217477.2 258000.0) (list 220477.2 258000.0) "" "H-400x200x8x13" "")
  (setvar "CLAYER" oldlayer)
  (princ)
)
